FME workspace EntryScape_replace_file_generic.fmw
Title: Ersättning av fil hos Entryscape
Description: Schemat används för att ersätta filer i öppna data-systemet Entryscape för kommuner.
När en datamängd har skapats och en fil laddats upp kan detta schema används för att per automatik ersätta filen i systemet.
/André Parviainen, Borås stad
andre.parviainen##boras.se 
2021-04-15

Parameters:
- URL_Domain =   # Domain (e.g. "https://data.zg.ch/")
- username =   # Username
- password =   # Password
- filename =   # Filepath
- auth_url = $(URL_Domain)store/auth/cookie
- store =   # store (e.g. "2")
- URI_file_distribution =   # URI_file_distribution (e.g. "38")
- URI_metadata_distribution =   # URI_metadata_distribution (e.g. "39")
- URI_metadata_resource = $(URL_Domain)store/$(store)/resource/
- URL_meta = $(URL_Domain)store/$(store)/metadata/$(URI_metadata_distribution)

Note: Input Parameters / Domain (e.g. "https://data.zg.ch/") / Domain of your catalog (including "/" at the end) / Username / your username / Password / your password / Filepath / Path of the file you want to upload / store (e.g. "2") / ID of your store / URI_file_distribution (e.g. "38") / from the distribution tab "Information" in Entryscape / URI_metadata_distribution (e.g. "39") / from the distribution tab "About" in Entryscape
Creator
    GEOMTYPE = Geometry Object
    NUM = 1
    CREATED -> StringConcatenator
StringConcatenator
    ACTION = Create New Attribute
    PARM_LINE = fme_basicstring:14%11%15%11%20:auth_username=$(username)&auth_password=$(password)&auth_maxage=604800&
    VAL_ATTR = login_parameters
    -> Authentication
Note: creates auth-token
Authentication: HTTPCaller
    CONNECTION_TIMEOUT_LENGTH = 60
    CUSTOM_HEADERS = Accept;application/json
    ERROR_ATTR = _error
    FOLLOW_REDIRECTS = FOLLOW_WITH_ORIGINAL_METHOD
    HTTP_METHOD = POST
    REDIRECT_AUTH = UNRESTRICTED
    SAVE_FILE = Attribute
    STATUS_CODE_ATTR = _http_status_code
    TARGET_ATTR = _response_body
    TARGET_ATTR_ENCODING = auto-detect
    TARGET_URL = $(auth_url)
    TRANSFER_TIMEOUT_LENGTH = 90
    UPLOAD_BODY = @Value(login_parameters)
    UPLOAD_CONTENT_TYPE = JSON (application/json)
    UPLOAD_TYPE = Specify Upload Body
    USE_COOKIES = Yes
    VERIFY_SSL_CERTIFICATES = Yes
    -> StringConcatenator_2
StringConcatenator_2
    ACTION = Create New Attribute
    PARM_LINE = fme_basicstring:26%8%10%24: https://data.zg.ch/store/$(store)/resource/$(URI_file_distribution)
    VAL_ATTR = result_URL
    -> UpdateFile_2
Note: replaces file
UpdateFile_2: HTTPCaller
    ADDITIONAL_URL_PARAMETERS = method;put textarea;true
    AUTH_METHOD = Single Sign-On
    CONNECTION_TIMEOUT_LENGTH = 60
    CUSTOM_HEADERS = Accept;application/json Cookie;
    ERROR_ATTR = _error
    FOLLOW_REDIRECTS = FOLLOW_WITH_GET
    HTTP_METHOD = POST
    MULTIPARTS = ----WebKitFormBoundarylt8wfmSn9KN7NmDR FileUpload SOURCE_FILE;$(filename);MIME_TYPE;application/octet-stream;FME_CONTROLLER_QUERY_FILE;transformers/dependencies/http/FileUpload.fme;FME_CONTROLLER_CHOICE;FileUpload
    REDIRECT_AUTH = ORIGINAL_DOMAIN_ONLY
    SAVE_FILE = Attribute
    STATUS_CODE_ATTR = _http_status_code
    TARGET_ATTR = _response_body
    TARGET_ATTR_ENCODING = auto-detect
    TARGET_URL = @Value(result_URL)
    TRANSFER_TIMEOUT_LENGTH = 90
    UPLOAD_TYPE = Multipart / Form Data
    USE_COOKIES = Yes
    VERIFY_SSL_CERTIFICATES = Yes
    -> DateTimeStamper
Note: rewrites "modification date" of distribution
UpdateDate_2: HTTPCaller
    CONNECTION_TIMEOUT_LENGTH = 60
    CUSTOM_HEADERS = Cookie;
    ERROR_ATTR = _error
    FOLLOW_REDIRECTS = FOLLOW_WITH_GET
    HTTP_METHOD = PUT
    REDIRECT_AUTH = ORIGINAL_DOMAIN_ONLY
    SAVE_FILE = Attribute
    STATUS_CODE_ATTR = _http_status_code
    TARGET_ATTR = _response_body
    TARGET_ATTR_ENCODING = auto-detect
    TARGET_URL = $(URL_meta)
    TRANSFER_TIMEOUT_LENGTH = 90
    UPLOAD_BODY:
      {"$(URI_metadata_resource)$(URI_metadata_distribution)":{
      "http://purl.org/dc/terms/license":[{"type":"uri","value":"http://dcat-ap.de/def/licenses/cc-zero"}],
      "http://purl.org/dc/terms/format":[{"type":"literal","value":"text/plain"}],
      "http://www.w3.org/ns/dcat#downloadURL":[{"type":"uri","value":"https://data.zg.ch/store/$(store)/resource/$(URI_file_distribution)"}],
      "http://www.w3.org/ns/dcat#accessURL":[{"type":"uri","value":"https://data.zg.ch/store/$(store)/resource/$(URI_file_distribution)"}],
      "http://www.w3.org/1999/02/22-rdf-syntax-ns#type":[{"type":"uri","value":"http://www.w3.org/ns/dcat#Distribution"}],
      "http://purl.org/dc/terms/rights":[{"type":"literal","value":"NonCommercialAllowed-CommercialAllowed-ReferenceNotRequired"}],
      "http://purl.org/dc/terms/modified":[{"type":"literal","value":"@Value(_timestamp).236Z","datatype":"http://www.w3.org/2001/XMLSchema#date"}]}}  ...
    UPLOAD_CONTENT_TYPE = JSON (application/json)
    UPLOAD_TYPE = Specify Upload Body
    USE_COOKIES = Yes
    VERIFY_SSL_CERTIFICATES = Yes
    -> UpdateDate_Output
UpdateDate_Output: Inspector

Bookmark: Erstellen von Zeitattributen zur Aktualisierung von Metadaten
Note: DateTimeStamper
DateTimeStamper
    DATETIME_ATTR = _timestamp
    INCLUDE_OFFSET = YES
    STAMP_TYPE = datetime
    TIMEZONE = local
    -> DateTimeConverter
Note: DateTimeConverter
DateTimeConverter
    DATETIME_ATTR = _timestamp
    OUT_FORMAT = %Y-%m-%dT%H:%M:00
    PASSTHROUGH = NO
    REPAIR_INPUT = YES
    -> UpdateDate_2
